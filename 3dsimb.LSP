(defun c:3dsimb ()
  (command"_plan" "")
  (setq gr  (ssget "x" (list '(0 . "POLYLINE")'(8 . "3dsimb"))))
  (if gr (command"_erase" gr ""))
				   
  (setq grrinf-b (ssget "x" (list '(0 . "INSERT") '(2 . "rinforzo-*"))))
  (setq grfori-b (ssget "x" (list '(0 . "INSERT") '(2 . "FORO*"))))
  (setq grrinf-m (ssget "x" (list '(0 . "MLINE") '(8 . "rinforzi") '(2 . "RINFORZO-*"))))
  (setq nr -1)
  (while (and grfori-b (setq foro (ssname grfori-b (setq nr ( + 1 nr)))))
    (setq hforo (atof (cdr (assoc '1 (entget (entnext foro))))))
    (command"_move" foro "" "_non" (list 0 0 (caddr (cdr (assoc '10 (entget foro))))) "_non" (setq pforo (list 0 0 hforo)))
    (setq pforo (cdr (assoc '10 (entget foro))))
    (setq prese (carica "prese" ""))
    (setq nforo (cdr (assoc '1 (entget (entnext (entnext foro))))))
    (setq nforo (substr nforo 1 8))
    (setq angforo (cdr (assoc '50 (entget foro))))
;;;    (val-l "3dfori")
    (command"_layer" "_n" "3dsimb" "")
    (command"_3dpoly" "_non" (list (car (polar pforo angforo (/ (nth 5 (assoc nforo prese)) 2)))
				 (cadr (polar pforo angforo (/ (nth 5 (assoc nforo prese)) 2)))
				 (- hforo (/ (nth 6 (assoc nforo prese)) 2))
				 )
	    "_non" (list (car (polar pforo (- angforo pi) (/ (nth 5 (assoc nforo prese)) 2)))
				 (cadr (polar pforo (- angforo pi) (/ (nth 5 (assoc nforo prese)) 2)))
				 (- hforo (/ (nth 6 (assoc nforo prese)) 2))
				 )
	     "_non" (list (car (polar pforo (- angforo pi) (/ (nth 5 (assoc nforo prese)) 2)))
				 (cadr (polar pforo (- angforo pi) (/ (nth 5 (assoc nforo prese)) 2)))
				 (+ hforo (/ (nth 6 (assoc nforo prese)) 2))
				 )
	    "_non" (list (car (polar pforo angforo (/ (nth 5 (assoc nforo prese)) 2)))
				 (cadr (polar pforo angforo (/ (nth 5 (assoc nforo prese)) 2)))
				 (+ hforo (/ (nth 6 (assoc nforo prese)) 2))
				 )
	    "_c")
    (command"_chprop" (entlast) "" "_la" "3dsimb" "_co" "2" "")
    )
    (setq nr -1)

  (while (and grrinf-b (setq foro (ssname grrinf-b (setq nr ( + 1 nr)))))
    (setq lrin (atof (leggi foro "HRIN")))
    (setq pforo (cdr (assoc '10 (entget foro))))
    (setq pan (ssget "_C" (list (- (car pforo) 1) (- (cadr pforo) 1) 0) (list (+ (car pforo) 1) (+ (cadr pforo) 1) 0) (list '(0 . "LWPOLYLINE") '(8 . "pannelli-*"))))
    (setq hpan (cdr (assoc '39 (entget (ssname pan 0)))))
    (setq hrin (- hpan (* 2 (cadr (assoc 'diffaltrinv parametri)))))
    (setq nforo (cdr (assoc '1 (entget (entnext (entnext foro))))))
    (setq angforo (cdr (assoc '50 (entget foro))))
;;;    (val-l "3dfori")
    (command"_layer" "_n" "3dsimb" "")
    (command"_3dpoly" "_non" (list (car (polar pforo angforo (/ lrin 2)))
				 (cadr (polar pforo angforo (/ lrin 2)))
				 (cadr (assoc 'diffaltrinv parametri))
				 )
	    "_non" (list (car (polar pforo (- angforo pi) (/ lrin 2)))
				 (cadr (polar pforo (- angforo pi) (/ lrin 2)))
				 (cadr (assoc 'diffaltrinv parametri))
				 )
	     "_non" (list (car (polar pforo (- angforo pi) (/ lrin 2)))
				 (cadr (polar pforo (- angforo pi) (/ lrin 2)))
				 (- hpan (cadr (assoc 'diffaltrinv parametri)))
				 )
	    "_non" (list (car (polar pforo angforo (/ lrin 2)))
				 (cadr (polar pforo angforo (/ lrin 2)))
				 (- hpan (cadr (assoc 'diffaltrinv parametri)))
				 )
	    "_c")
    (command"_chprop" (entlast) "" "_la" "3dsimb" "_co" "5" "")
    
    )
  (setq nr -1)
  (while (and grrinf-m (setq foro (ssname grrinf-m (setq nr ( + 1 nr)))))
    (setq hrin (atof (leggi foro "HRIN")))
    (setq p2rin (cdr (assoc '11 (cdr (member (assoc '11 (entget foro)) (entget foro))))))
    (setq pforo (cdr (assoc '11 (entget foro))))
;;;    (val-l "3dfori")
    (command"_layer" "_n" "3dsimb" "")
    (command"_3dpoly" "_non" (list (car pforo)
				 (cadr pforo)
				 (- (caddr pforo) (/ hrin 2))
				 )
	    "_non" (list (car p2rin)
				 (cadr p2rin)
				 (- (caddr p2rin) (/ hrin 2))
				 )
	     "_non" (list (car p2rin)
				 (cadr p2rin)
				 (+ (caddr p2rin) (/ hrin 2))
				 )
	    "_non" (list (car pforo)
				 (cadr pforo)
				 (+ (caddr pforo) (/ hrin 2))
				 )
	    "_c")
    (command"_chprop" (entlast) "" "_la" "3dsimb" "_co" "5" "")
    
    )
	      (command"_zoom" "_p")
)
