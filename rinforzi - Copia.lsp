(defun c:rinforzov ()
  (start)
  ;PPP
  (setq rinforzi (carica "rinforzi" ""))
  (setq nblo (getstring "\nNome rinforzo verticale: "))
  (prompt"\nPunto di inserimento: ")
  (command"_insert" nblo "s" 1 pause pause)
    (setq rigar (assoc (substr nblo 10 2) rinforzi))
  (if (null rigar) (progn (alert "rinforzo mancante i rinforzi.txt") (exit)))
  (if (= 0 (nth 1 rigar))
    (progn
      (setq hrinforzo (getdist "\nAltezza del rinforzo <150> :"))
      (if (null hrinforzo) (setq hrinforzo 150))
      )
    (setq hrinforzo (nth 1 rigar))
    )
	(allega (entlast) "HRIN" (rtos hrinforzo 2 0))

  )
  
(defun c:rinforzo ()
  (start)
  ;PPP
  (setq rinforzi (carica "rinforzi" ""))
  (setq distrf (cadr (assoc 'arretrinf parametri)))
  (SETQ STYLEML (GETSTRING "\nCodice rinforzo:"))
  (setq hrin (getdist "\nAltezza dal pavimento <900> :"))
  (if (null hrin) (setq hrin 900))
  (setq rigar (assoc STYLEML rinforzi))
;  (setq gr (ssget (list '(0 . "LWPOLYLINE") '(8 . "pannelli-dritti"))))
  (if (null rigar) (progn (alert "rinforzo mancante i rinforzi.txt") (exit)))
  (if (= 0 (nth 1 rigar))
    (progn
      (setq hrinforzo (getdist "\nAltezza del rinforzo <150> :"))
      (if (null hrinforzo) (setq hrinforzo 150))
      )
    (setq hrinforzo (nth 1 rigar))
    )
  (setq nr 0)
  (setq gr (ssget (list '(0 . "LWPOLYLINE") '(8 . "pannelli-*"))))
  (COMMAND"_LAYER" "_M" "rinforzi" "")
  (while (setq ent (ssname gr nr))
    (if (=  "pannelli-dritti" (cdr (assoc '8 (entget ent))))
      (progn
	(SETQ LISPT NIL)
	(FOREACH N (ENTGET ent)
	  (IF (= '10 (CAR N)) (SETQ LISPT (CONS (CDR N) LISPT)))
	)
	(setq lispt (reverse lispt))
	(SETQ ANG (ANGLE (NTH 0 LISPT) (NTH 1 LISPT)))
	(command"_elev" hrin 0)
	(command"_mline" "_sT" (STRCAT "RINFORZO-" STYLEML) "_J" "_B" "_NON" (POLAR (POLAR (NTH 0 LISPT) ANG distrf) (+ ANG (/ PI 2)) 0.7)
	                                             "_NON" (POLAR (POLAR (NTH 1 LISPT) (+ ANG PI) distrf) (+ ANG (/ PI 2)) 0.7) ""
	)
	(allega (entlast) "HRIN" (rtos hrinforzo 2 0))
      )
      (progn
	(SETQ LISPT NIL)
	(FOREACH N (ENTGET ent)
	  (IF (= '10 (CAR N)) (SETQ LISPT (CONS (CDR N) LISPT)))
	)
	(setq lispt (reverse lispt))
	(SETQ ANG1 (ANGLE (NTH 0 LISPT) (NTH 1 LISPT)))
	(SETQ ANG2 (ANGLE (NTH 1 LISPT) (NTH 2 LISPT)))
	(command"_elev" hrin 0)
	(command"_mline" "_sT" (STRCAT "RINFORZO-" STYLEML) "_J" "_B" "_NON" (POLAR (POLAR (NTH 0 LISPT) ANG1 distrf) (+ ANG1 (/ PI 2)) 0.7)
	                                             "_NON" (POLAR (POLAR (NTH 1 LISPT) (+ ANG1 PI) distrf) (+ ANG1 (/ PI 2)) 0.7) ""
	)
		(allega (entlast) "HRIN" (rtos hrinforzo 2 0))

	(command"_mline" "_sT" (STRCAT "RINFORZO-" STYLEML) "_J" "_B" "_NON" (POLAR (POLAR (NTH 1 LISPT) ANG2 distrf) (+ ANG2 (/ PI 2)) 0.7)
	                                             "_NON" (POLAR (POLAR (NTH 2 LISPT) (+ ANG2 PI) distrf) (+ ANG2 (/ PI 2)) 0.7) ""
	)
		(allega (entlast) "HRIN" (rtos hrinforzo 2 0))

      )
    )
    (setq nr (+ 1 nr))
  )
  (COMMAND"_LAYER" "_M" "0" "")
  (stop)
)
