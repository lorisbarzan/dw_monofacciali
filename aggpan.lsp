(defun c:Aggpan ()
  (carica "parametri" "")
  (setq godis nil)
  (c:apdia)
  (if (= a 1)
    (progn
      (setq nfilea (strcat (cadr (assoc 'percregtmp parametri)) "anagraf.txt"))
      (setq nfiled (strcat (cadr (assoc 'percregtmp parametri)) "distbase.txt"))
      (setq modalita (cadr (assoc 'percregtmp parametri)))
      (setq revisione ".00")
      (setq filea (S_OPEN nfilea "a"))
      (setq filed (S_OPEN nfiled "a"))
      (setq orainizio (getvar"cdate"))
      (setq go! t)
      (aggPAN)
        (s_close filea nfilea)
  (s_close filed nfiled)
  (setq orafine (getvar"cdate"))
  (prompt (strcat "\nSecondi impiegati per registrazione :" (rtos (* 1000000 (- (atof (rtos orafine 2 6)) (atof (rtos orainizio 2 6)))) 2 1)))

    )
  )
  (if (= a 2)
    (progn
  (initget "Si No")
  (if (= "Si" (getkword "\nVuoi procedere con la registrazione definitiva [Si/No] <No>:"))
    (progn
      (setq nfilea (cadr (assoc 'fileanagrafica parametri)))
      (setq nfiled (cadr (assoc 'filedistbase parametri)))
      (setq nfiled6 (strcat (cadr (assoc 'filedistbase parametri)) "6"))
      (setq modalita (cadr (assoc 'percregdef parametri)))
      (foreach n '("cabine" "cabpan" "dibpan" "dibpas" "pannelli"
		   "pannellil" "DIBsvi" "sviluppi" "DIBLDR" "mater" 
		   "DIBrin" )
	(vl-file-delete (strcat modalita n ".bak"))
	(if (null (vl-file-copy (strcat modalita n ".txt") (strcat modalita n ".bak")))
	  (progn (alert (strcat "File " n " Non accessibile")) (exit))
	  )
	)
      (vl-file-delete
	(strcat (vl-filename-directory (cadr (assoc 'fileanagrafica parametri)))"/"(vl-filename-base (cadr (assoc 'fileanagrafica parametri)))".bak")
	)
      
      (if (null (vl-file-copy (cadr (assoc 'fileanagrafica parametri))
		  (strcat (vl-filename-directory (cadr (assoc 'fileanagrafica parametri)))"/"(vl-filename-base (cadr (assoc 'fileanagrafica parametri)))".bak")
		  )
		)
	(progn (alert "File Anagrafica non accessibile") (exit))
	)
      (vl-file-delete
	(strcat (vl-filename-directory (cadr (assoc 'filedistbase parametri)))"/"(vl-filename-base (cadr (assoc 'filedistbase parametri)))".bak")
	)
      (if (null (vl-file-copy (cadr (assoc 'filedistbase parametri))
		  (strcat (vl-filename-directory (cadr (assoc 'filedistbase parametri)))"/"(vl-filename-base (cadr (assoc 'filedistbase parametri)))".bak")
		  )
		)
	(progn (alert "File Distbase non accessibile")(exit))
	)
      (setq filea (S_OPEN nfilea "a"))
      (setq filed (S_OPEN nfiled "a"))
      (setq orainizio (getvar"cdate"))
      ;;;  (setq seltravinf (selezpar 'traversinf "traversina inferiore"))
      ;;;  (setq seltravsup (selezpar 'traverssup "traversina Superiore"))
      ;;;;;;;;;;;;;;;;;;;;;;;;;;;;;;  (setq selrinfpiede (selezpar 'codrinfpiedep "Rinforzo piede"))
      ;;;;;;;;;;;;;;;;;;;;;;;;;;;;;;  (setq selvelovetro (selezpar 'velovetro "Velovetro"))
      ;;;;;;;;;;;;;;;;;;;;;;;;;;;;;;  (setq sellanacer (selezpar 'lanaceramica "Lana Ceramica"))
      ;;;;;;;;;;;;;;;;;;;;;;;;;;;;;;  (setq revisione (getstring "\nRevisione nr [.00/.01/.02/.03/.04] <.00>:"))
      (setq go! t)
      (aggPAN)
      (s_close filea nfilea)
      (s_close filed nfiled)
      (setq orafine (getvar"cdate"))
      (prompt (strcat "\nSecondi impiegati per registrazione :" (rtos (* 1000000 (- (atof (rtos orafine 2 6)) (atof (rtos orainizio 2 6)))) 2 1)))

      )
      )
    )
    
  )
  
)


;;;  (carica "parametri" "")

(defun c:apdia ()
  (setq nrdl (load_dialog "aggpan"))
  
  (new_dialog "aggpan" nrdl)
  (set_tile "lung" (rtos (cadr (assoc 'lungpannello parametri)) 2 0))
  (set_tile "lung2" "0")
;;;  (set_tile "angpan1" "90")
;;;  (set_tile "angpan2" "90")
  (set_tile "angpan" "0")
  (set_tile "halt" "2200")
  (start_list "resis") (add_list "B0") (add_list "B0+") (add_list "B15")(add_list "B15+")  (end_list)
  (if (findfile (strcat modalita "$$.txt"))
    (progn
      (setq filex (open (strcat modalita "$$.txt") "r"))
      (read-line filex)
      (setq lis (read-line filex))
      (close filex)
      )
    (progn
      (setq lis (cadr (assoc 'FINITURE parametri)))
      (repeat 15 (setq lis (vl-string-subst "\" \"" "/" lis)))
       (setq lis (strcat "(\"" lis "\")"))
      )
    )
  
  (setq lisfin (read lis))
  (start_list "finit")   (foreach n lisfin (add_list n)) (end_list)

  (Setq listip '( "STD" "SFT" "SPC" "SPS" "SPD" "ATD" "APC" "APS" "APD" "SSC" "SSS" "SSD"
    "SFC" "SFS" "SFD" "BTD" "BPC" "BPS" "BPD" "ITD"
    "IPC" "IPS" "IPD" "MAN" "MTD" "MPC" "MPS" "MPD"))
  (start_list "modop") (foreach n listip (add_list n)) (end_list)
  (setq lisrpi (cdr (assoc 'CODRINFPIEDEP parametri)))
;;;  (start_list "selrinfpiede") (foreach n lisrpi (add_list n)) (end_list)
;;;  (setq lisvel (cdr (assoc 'VELOVETRO parametri)))
;;;  (start_list "selvelovetro") (foreach n lisvel (add_list n)) (end_list)
;;;  (setq lislce (cdr (assoc 'LANACERAMICA parametri)))
;;;  (start_list "sellanacer") (foreach n lislce (add_list n)) (end_list)
;rinforzi  
  (setq rinforzi (carica "rinforzi" ""))
  (setq lrf '("")) (foreach n (cdr rinforzi) (if (= 3 (length n))(setq lrf (cons (car n) lrf))))
  (setq lrf (reverse lrf))
  (start_list "n1r") (foreach n lrf (add_list n)) (end_list)
  (start_list "n2r") (foreach n lrf (add_list n)) (end_list)
  (start_list "n3r") (foreach n lrf (add_list n)) (end_list)
  (start_list "n4r") (foreach n lrf (add_list n)) (end_list)
  (action_tile "n1r" "(comprinf \"1r\")")
  (action_tile "n2r" "(comprinf \"2r\")")
  (action_tile "n3r" "(comprinf \"3r\")")
  (action_tile "n4r" "(comprinf \"4r\")")
;;;  (set_tile "x1r" "8")  (set_tile "x2r" "8")  (set_tile "x3r" "8")  (set_tile "x4r" "8")
  (setq prese (carica "prese" ""))
  (setq lpr '("")) (foreach n (cdr prese) (setq lpr (cons (car n) lpr)))
  (setq lpr (reverse lpr))
  (start_list "n1f") (foreach n lpr (add_list n)) (end_list)
  (start_list "n2f") (foreach n lpr (add_list n)) (end_list)
  (start_list "n3f") (foreach n lpr (add_list n)) (end_list)
  (start_list "n4f") (foreach n lpr (add_list n)) (end_list)
  (action_tile "n1f" "(compforo \"1f\")")
  (action_tile "n2f" "(compforo \"2f\")")
  (action_tile "n3f" "(compforo \"3f\")")
  (action_tile "n4f" "(compforo \"4f\")")
  (action_tile "ric" "(ricomp)")
;  (action_tile "ante" "(legginput) (aggpan)")
  (action_tile "accept" "(legginput) (done_dialog 1)")
  (action_tile "regdef" "(legginput) (done_dialog 2)")
  (action_tile "ante" "(legginput) (vermod)")
  (action_tile "sal" "(legginput)")
  (action_tile "modop" "(leggitip)")
  (setq a (start_dialog))
)
(defun leggitip ()
  (setq modop (nth (atoi (setq nmodop (get_tile "modop"))) listip))
  (if (= "MAN" modop)
    (progn
      (new_dialog "tip_man" nrdl)
      (action_tile "accept" "(setq man_ag1 (atof (get_tile \"man_ag1\"))) (setq man_ag2 (atof (get_tile \"man_ag2\"))) (setq man_agh (atof (get_tile \"man_agh\"))) (done_dialog 1)")
      (setq a (start_dialog))
      (if (= a 0) (setq man_ag1 0 man_ag2 0 man_agh 0))
    )
  )
)

(defun vermod ()
  (if (ssget "x" (list '(0 . "TEXT") '(1 . "NOTA: LA VISTA DEL PANNELLO E' DAL LATO DELLA")))
      (progn (setq godis t) (done_dialog 1))
      (progn (alert "Non sei nel prototipo giusto !!") (setq godis nil))
  )
)
(defun compforo (nr)
  (if (= "0" (get_tile (strcat "n" nr)))
    (progn
      (set_tile (strcat "x" nr) "")
      (set_tile (strcat "y" nr) "")
    )
    (progn
      (set_tile (strcat "x" nr) "100")
      (set_tile (strcat "y" nr) "1120")
    )
  )
)
(defun comprinf (nr)
  (if (= "0" (get_tile (strcat "n" nr)))
    (progn
      (set_tile (strcat "x" nr) "")
      (set_tile (strcat "y" nr) "")
      (set_tile (strcat "l" nr) "")
    )
    (progn
      (set_tile (strcat "x" nr) "8")
      (set_tile (strcat "y" nr) "1600")
      (set_tile (strcat "l" nr) (rtos (- (atof (get_tile "lung")) 16) 2 0))
    )
  )
)
(defun ricomp ()
  (set_tile "desc-pas" desc-pas)
  (set_tile "desc-pan" desc-pan)
  
  (set_tile "lung" (rtos lung 2 1))
  (set_tile "lung2" (rtos lung2 2 1))
  (set_tile "angpan" (rtos Angpan 2 0))
  (set_tile "halt" (rtos halt 2 0))
  (set_tile "angpan1" (rtos Angpan1 2 0))
  (set_tile "angpan2" (rtos Angpan2 2 0))
  (set_tile "finit" nfinit)
  (set_tile "modop" nmodop)
  (set_tile "resis" nresis)
;;;  (set_tile "selrinfpiede" nselrinfpiede)
;;;  (set_tile "selvelovetro" nselvelovetro)
;;;  (set_tile "sellanacer" nsellanacer)
  (if (/= "0" nn1r) (progn (set_tile "n1r" nn1r) (set_tile "l1r" (rtos (nth 1 (nth 0 bl_lrin)) 2 1)) (set_tile "x1r" (rtos (nth 2 (nth 0 bl_lrin)) 2 1))
      (set_tile "y1r" (rtos (nth 3 (nth 0 bl_lrin)) 2 1))))
  
  (if (/= "0" nn2r) (progn (set_tile "n2r" nn2r) (set_tile "l2r" (rtos (nth 1 (nth 1 bl_lrin)) 2 1)) (set_tile "x2r" (rtos (nth 2 (nth 1 bl_lrin)) 2 1))
      (set_tile "y2r" (rtos (nth 3 (nth 1 bl_lrin)) 2 1))))

  (if (/= "0" nn3r) (progn (set_tile "n3r" nn3r) (set_tile "l3r" (rtos (nth 1 (nth 2 bl_lrin)) 2 1)) (set_tile "x3r" (rtos (nth 2 (nth 2 bl_lrin)) 2 1))
      (set_tile "y3r" (rtos (nth 3 (nth 2 bl_lrin)) 2 1))))

  (if (/= "0" nn4r) (progn (set_tile "n4r" nn4r) (set_tile "l4r" (rtos (nth 1 (nth 3 bl_lrin)) 2 1)) (set_tile "x4r" (rtos (nth 2 (nth 3 bl_lrin)) 2 1))
      (set_tile "y4r" (rtos (nth 3 (nth 3 bl_lrin)) 2 1))))

  (if (/= "0" nn1f) (progn (set_tile "n1f" nn1f)  (set_tile "x1f" (rtos (nth 1 (nth 0 bl_lfor)) 2 1)) (set_tile "y1f" (rtos (nth 2 (nth 0 bl_lfor)) 2 1))))
  (if (/= "0" nn2f) (progn (set_tile "n2f" nn2f)  (set_tile "x2f" (rtos (nth 1 (nth 1 bl_lfor)) 2 1)) (set_tile "y2f" (rtos (nth 2 (nth 1 bl_lfor)) 2 1))))
  (if (/= "0" nn3f) (progn (set_tile "n3f" nn3f)  (set_tile "x3f" (rtos (nth 1 (nth 2 bl_lfor)) 2 1)) (set_tile "y3f" (rtos (nth 2 (nth 2 bl_lfor)) 2 1))))
  (if (/= "0" nn4f) (progn (set_tile "n4f" nn4f)  (set_tile "x4f" (rtos (nth 1 (nth 3 bl_lfor)) 2 1)) (set_tile "y4f" (rtos (nth 2 (nth 3 bl_lfor)) 2 1))))
  
)
  
(DEFUN LEGGINPUT ()
     (setq desc-pas (get_tile "desc-pas"))
     (setq desc-pan (get_tile "desc-pan"))
     (setq lung (atof (GET_TILE "lung")))
     (setq lung2 (atof (GET_TILE "lung2")))
     (setq Angpan (atof (GET_TILE "angpan")))
     (setq halt (atof (get_tile "halt")))
;;;     (setq angpan1 (atof (GET_TILE "angpan1")))
;;;     (setq angpan2 (atof (GET_TILE "angpan2")))
     (setq finit (nth (atoi (setq nfinit (get_tile "finit"))) lisfin))
     (setq modop (nth (atoi (setq nmodop (get_tile "modop"))) listip))
;     (if (= "0" (setq nresis (get_tile "resis"))) (setq resis "B0") (setq resis "B15"))
     (cond ((= "0" (setq nresis (get_tile "resis"))) (setq resis "B0"))
	   ((= "1" (setq nresis (get_tile "resis"))) (setq resis "B0+"))
	   ((= "2" (setq nresis (get_tile "resis"))) (setq resis "B15"))
	   ((= "3" (setq nresis (get_tile "resis"))) (setq resis "B15+"))
	   )
;;;     (setq selrinfpiede (nth (atoi (setq nselrinfpiede (get_tile "selrinfpiede"))) lisrpi))
;;;     (setq selvelovetro (nth (atoi (setq nselvelovetro (get_tile "selvelovetro"))) lisvel))
;;;     (setq sellanacer (nth (atoi (setq nsellanacer (get_tile "sellanacer"))) lislce))
;          (setq bl_lrin '(("nome" 200 45 900)))
     (setq bl_lrin nil)
     (if (/= "0" (setq nn1r (get_tile "n1r")))
       (progn
	 (setq bl_lrin (cons (list (nth (atoi (get_tile "n1r")) lrf) (atof (get_tile "l1r")) (atof (get_tile "x1r"))  (atof (get_tile "y1r"))) bl_lrin))
       )
     )
     (if (/= "0" (setq nn2r (get_tile "n2r")))
       (progn
	 (setq bl_lrin (cons (list (nth (atoi (get_tile "n2r")) lrf) (atof (get_tile "l2r")) (atof (get_tile "x2r"))  (atof (get_tile "y2r"))) bl_lrin))
       )
     )
     (if (/= "0" (setq nn3r (get_tile "n3r")))
       (progn
	 (setq bl_lrin (cons (list (nth (atoi (get_tile "n3r")) lrf) (atof (get_tile "l3r")) (atof (get_tile "x3r"))  (atof (get_tile "y3r"))) bl_lrin))
       )
     )
     (if (/= "0" (setq nn4r (get_tile "n4r")))
       (progn
	 (setq bl_lrin (cons (list (nth (atoi (get_tile "n4r")) lrf) (atof (get_tile "l4r")) (atof (get_tile "x4r"))  (atof (get_tile "y4r"))) bl_lrin))
       )
     )
     (if bl_lrin (setq bl_lrin (reverse bl_lrin)))
;fori
     (setq bl_lfor nil)
     (if (/= "0" (setq nn1f (get_tile "n1f")))
       (progn
	 (setq bl_lfor (cons (list (nth (atoi (get_tile "n1f")) lpr) (atof (get_tile "x1f"))  (atof (get_tile "y1f"))) bl_lfor))
       )
     )
     (if (/= "0" (setq nn2f (get_tile "n2f")))
       (progn
	 (setq bl_lfor (cons (list (nth (atoi (get_tile "n2f")) lpr) (atof (get_tile "x2f"))  (atof (get_tile "y2f"))) bl_lfor))
       )
     )
     (if (/= "0" (setq nn3f (get_tile "n3f")))
       (progn
	 (setq bl_lfor (cons (list (nth (atoi (get_tile "n3f")) lpr) (atof (get_tile "x3f"))  (atof (get_tile "y3f"))) bl_lfor))
       )
     )
     (if (/= "0" (setq nn4f (get_tile "n4f")))
       (progn
	 (setq bl_lfor (cons (list (nth (atoi (get_tile "n4f")) lpr) (atof (get_tile "x4f"))  (atof (get_tile "y4f"))) bl_lfor))
       )
     )
     (if bl_lfor (setq bl_lfor (reverse bl_lfor)))
;;;     (SETQ RESIS "B0")    
;;;     (SETQ MODOP "STD")
;;;  (if (= modop "MAN") (setq man_ag1 15 man_ag2 14 man_agh 20))
)


(defun Aggpan ();uno
  (SETQ NR 0)
  (setq lispan (carica_f "pannellil" modalita))
  (setq lispn $tb$)
  (setq DIBpan (carica_f "DIBpan" modalita))
  (setq DIBpn $tb$)
  (setq lispas (carica_f "pannelli" modalita))
  (setq lisps $tb$)
  (setq DIBpaS (carica_f "DIBpaS" modalita))
  (setq DIBpS $tb$)
  (setq fogli (carica "fogli" ""))
  (setq fogl $tb$)
  (setq sviluppi (carica_f "sviluppi" modalita))
  (setq svilupp $tb$)
  (setq DIBsvi (carica_f "DIBsvi" modalita))
  (setq DIBsv $tb$)
  (setq cesoiati (carica "cesoiati" modalita))
  (setq cesoiat $tb$)
  (setq lanadir (carica "lanadir" ""))
  (setq lanadi $tb$)
;;;  (setq lanacer (carica "lanacer" modalita))
;;;  (setq lanace $tb$)
  (setq mater (carica "mater" modalita))
  (setq mate $tb$)
;;;  (setq rinfpiede (carica "rinfpiede" modalita))
;;;  (setq rinfpied $tb$)
  (setq tabrinfor (carica "tabrinf" modalita))
  (setq tabrinfo $tb$)
  (SETQ DISTFORI (CARICA "DISTFORI" ""))
  (setq POSPON (carica "POSPONTI" ""))
  (setq nbasepas (substr (car (nth 1 LISPAS)) 1 5))
     (setq listap nil)
     (setq listaps nil)
     (setq spes 28)
  (if (or (= modop "SFC") (= modop "SFD")) (setq spes 28))
;;;     (if (/= 0 lung2) (setq llungrp (list (- lung (cadr (assoc 'diflungpiede parametri)))
;;;					  (- lung2 (cadr (assoc 'diflungpiede parametri)))
;;;			            )
;;;		      )
;;;                      (setq llungrp (list (- lung (cadr (assoc 'diflungpiede parametri)))))
;;;     )
;;;     (foreach lungrp llungrp
;;;            (setq rig_p (list "Rinforzo piede pannello" selrinfpiede (atof (rtos lungrp 2 1)) "Nr"))
;;;            (if (setq percod_p (member rig_p rinfpied))
;;;                (progn
;;;                   (setq nomerin (car (nth (- (LENGTH rinfpied) (length percod_p)) rinfpiede)))
;;;                )  
;;;                (progn
;;;  	           (setq file (S_OPEN (strcat modalita "rinfpiede.txt") "a"))
;;;  	           (setq newcod (rtos (+ 1 (atoi (substr (car (last rinfpiede)) 6))) 2 0))
;;;	           (repeat (- 5 (strlen newcod)) (setq newcod (strcat "0" newcod)))
;;;		   (setq n_base (substr (car (last RINFPIEDE)) 1 5))
;;;                   (setq rig-p (strcat "\"" n_base newcod "\"\t\"Rinforzo piede pannello\"\t\"" (NTH 1 RIG_p)"\"\t" (rtos (NTH 2 RIG_p) 2 1) "\t\"Nr\""))
;;;                   (SETQ nomerin (strcat n_base newcod))
;;;                   (IF REGP (SETQ RIG_A-p (strcat nomerin "|Rinforzo piede pannello|Nr.|" (rtos (nth 2 rig_p) 2 1) "|||Rinpiede|||||0|0||||"))
;;;		     (SETQ RIG_A-p (strcat nomerin "|Rinforzo piede pannello|Nr.|" (rtos (nth 2 rig_p) 2 1) "|||Rinpiede|||||"))
;;;		   )
;;;                   (if go! (write-line rig-p file))
;;;                   (s_close file (strcat modalita "rinfpiede.txt"))
;;;                   (setq rinfpiede (carica "rinfpiede" modalita))
;;;                   (setq rinfpied $tb$)
;;;                   (if go! (progn (write-line rig_A-p filea) (inquad rig_A-p)))
;;;                   (setq file (S_OPEN (strcat modalita "DIBrinp.txt") "a"))
;;;                   (setq rig (strcat "\"" nomerin "\"\t\"" (NTH 1 rig_p) "\"\t" (rtos (nth 2 rig_p) 2 1)))
;;;                   (if go! (write-line rig file))
;;;                   (s_close file (strcat modalita "DIBrinp.txt"))
;;;	           (SETQ RIG_A (STRCAT NOMErin "|" (NTH 1 rig_P) "|" (RTOS (/ (NTH 2 rig_P) 1000) 2 2) "||"))
;;;		   (SETQ RIG_A6 (STRCAT NOMErin "|" (NTH 1 rig_P) "|" (RTOS (/ (NTH 2 rig_P) 1000) 2 2) "||||"))
;;;		   
;;;                   (if go! (WRITE-LINE RIG_A FILED))
;;;		  (if go! (WRITE-LINE RIG_A6 FILED6))
;;;                )
;;;             )
;;;             (setq LISTAPs (cons (list NOMERIN 1 1 1 0 0) LISTAPs))
;;;      )
;------------	    
;sviluppi
     (setq svilpan (carica "svilpan" ""))
     (setq modoold modop)
     (setq modop (strcat "S" (substr modop 2)))
  (if (/= modop "SAN")
     (foreach m svilpan
       (if (and (= modop (car m)) (= finit (cadr m))) (setq lunglam (+ lung lung2 (nth 2 m) (nth 3 m))))
     )
     (setq lunglam (+ lung lung2 man_ag1 man_ag2))
  )
     (setq modop modoold)
(setq h1800 (cadr (assoc 'limitepiegavelette parametri)))
     (cond ((and (or (= modop "SFD") (= modop "SFS") (= modop "SFC") (= modop "SFT"))
	      (> h1800 halt)
	    )
            (SETQ HALT_F (+ HALT (* 2 (cadr (assoc 'piegavelette parametri)))))
	   )
	   ( (or (= modop "ATD") (= modop "APC") (= modop "APS") (= modop "APD"))
	     
	 
            (SETQ HALT_F (+ HALT (* 2 (cadr (assoc 'piegavelette parametri)))))
	   )
	   ((and (or (= modop "BTD") (= modop "BPS") (= modop "BPD") (= modop "BPC"))
	    )
            (SETQ HALT_F (+ HALT (* 1 (cadr (assoc 'piegavelette parametri)))))
	   )
	   ((and (or (= modop "ITD") (= modop "IPS") (= modop "IPD") (= modop "IPC"))
	    )
            (SETQ HALT_F (+ HALT (* 1 (cadr (assoc 'piegavelette parametri)))))
	   )
	   ((= modop "MAN")  (SETQ HALT_F (+ HALT man_agh)))
           (t (SETQ HALT_F HALT))
     )
     (if (= "MAN" modop) (setq halt_f_ 0) (setq halt_f_ halt_f))
    (setq len_f (assoc finit fogl))

     (if (null len_f) (progn (alert "Riga mancante in Fogli.txt!!") (exit)))
     (setq cod_f (car (nth (- (LENGTH FOGL) (length len_f)) fogli)))
     (setq cod_f finit)

  
     (setq rig_f (list (strcat "Pannello cesoiato " (nth 2 (assoc finit fogl))) cod_f (atof (rtos lunglam 2 1)) (atoi (rtos halt_f 2 0)) 0
		       (atoi (rtos (* (atof (rtos lunglam 2 1)) (atof (rtos halt_F 2 1))) 2 0)) "Nr" ))
     (if (null lunglam) (progn (alert "Riga mancante in Svilpan.txt!!") (exit)));31.03.04
     (if (setq percod_F (member rig_f cesoiat))
       (progn
         (setq nomepan_f (car (nth (- (LENGTH cesoiat) (length percod_f)) cesoiati)))
       )  
       (progn
	 (setq file (S_OPEN (strcat modalita "cesoiati.txt") "a"))
	 (setq newcod (rtos (+ 1 (atoi (substr (car (last cesoiati)) 6))) 2 0))
	 (repeat (- 5 (strlen newcod)) (setq newcod (strcat "0" newcod)))
	 (setq n_base (substr (car (last cesoiati)) 1 5))
         (setq rig-F (strcat "\"" n_base newcod "\"\t\"Pannello cesoiato "(nth 2 (assoc finit fogl)) "\"\t\"" (NTH 1 RIG_F)"\"\t" (rtos (NTH 2 RIG_f) 2 1)
			     "\t" (rtos (NTH 3 RIG_f)2 0) "\t" (RTOS (NTH 4 RIG_f) 2 0) "\t" (rtos (NTH 5 RIG_f) 2 0)
			     "\t\"" (NTH 6 RIG_f) "\"")
	 )
         (SETQ nomepan_F (strcat n_base newcod))
         (IF REGP (SETQ RIG_A-f (strcat nomepan_F "|Pannello cesoiato "(nth 2 (assoc finit fogl))"|Nr.|" (rtos (nth 2 rig_F) 2 1) "|" (rtos (nth 3 rig_f) 2 1) "|"(rtos (nth 4 rig_f) 2 0)
                           "|Cesoiato|" "|" finit "|" "|" "|0|0||||"
                         )		   
         )
	   (SETQ RIG_A-f (strcat nomepan_F "|Pannello cesoiato "(nth 2 (assoc finit fogl))"|Nr.|" (rtos (nth 2 rig_F) 2 1) "|" (rtos (nth 3 rig_f) 2 1) "|"(rtos (nth 4 rig_f) 2 0)
                           "|Cesoiato|" "|" finit "|" "|" "|"
                         )		   
         )
	   )
         (if go! (write-line rig-f file))
         (s_close file (strcat modalita "cesoiati.txt"))
         (setq cesoiati (carica "cesoiati" modalita))
         (setq cesoiat $tb$)
         (if go! (progn (write-line rig_A-f filea) ;(inquad rig_A-f)
		   ))
         (setq file (S_OPEN (strcat modalita "DIBces.txt") "a"))
         (setq rig (strcat "\"" nomePAN_f "\"\t\"Materiale finitura " (NTH 1 rig_f) "\"\t" (RTOS (NTH 2 rig_f) 2 0)
                              "\t" (RTOS (NTH 3 rig_f) 2 0) "\t" (RTOS (NTH 4 rig_f) 2 0) "\t" (RTOS (NTH 5 rig_f) 2 0)))
         (if go! (write-line rig file))
	 (SETQ RIG_A (STRCAT NOMEPAN_f "|Materiale finitura " (NTH 1 rig_f) "|" (RTOS (/ (atof (rtos (NTH 5 rig_f))) 1000000) 2 2) "||"))

	 (if go! (WRITE-LINE RIG_A FILED))
	 
         (s_close file (strcat modalita "DIBces.txt"))
       )
     )
     (setq listap (cons (list nomepan_f 0 0 1 0 0) listap))
;fori
     (SETQ FORISN "No")
     (setq grf nil)
     (setq prese (carica "prese" ""))
     (IF bl_lfor
       (PROGN
         (SETQ FORISN "Si")
	 (SETQ NRF 0)
	 (foreach bl_for bl_lfor
	    (setq nfor (nth 0 bl_for))
	    (setq xfor (nth 1 bl_for))
	    (setq yfor (nth 2 bl_for))
	    (SETQ DFOR "Scatola portafrutti")
	    (SETQ NRF (+ 1 NRF))
            (SETQ LFOR (LIST "000000000" (NTH 2 (ASSOC NFOR PRESE)) (NTH 3 (ASSOC NFOR PRESE)) 1 (ATOF (RTOS XFOR 2 1)) (ATOF (RTOS YFOR 2 1))))
            (SETQ LISTAP (CONS LFOR LISTAP))
	  )     
       )
       (SETQ FORISN "No")
     )
;fine fori
;INIZIO RINFOEZI
     (setq rinfsn "No")
     (setq grr nil)
     (IF bl_lrin
       (PROGN
         (SETQ rinfsn "Si")
	  (SETQ NRF 0)
	  (setq listar nil)
	  (foreach bl_rin bl_lrin ;WHILE (SETQ ENTF (SSNAME GRr NRF))
	    (SETQ Nrin (nth 0 bl_rin))
	    (setq lgrin (nth 1 bl_rin))
	    (setq drin (strcat "Rinforzo " Nrin))
	    (setq lrin (list nrin drin lgrin))
	    (setq xrin (nth 2 bl_rin))
    	    (setq listar nil)
            (setq rig_p (list "Rinforzo pannello" nrin lgrin "Nr"))
	    
            (if (setq percod_p (member rig_p tabrinfo))
                (progn
                   (setq nomerin (car (nth (- (LENGTH tabrinfo) (length percod_p)) tabrinfor)))
                )  
                (progn
  	           (setq file (S_OPEN (strcat modalita "tabrinf.txt") "a"))
  	           (setq newcod (rtos (+ 1 (atoi (substr (car (last tabrinfor)) 6))) 2 0))
	           (repeat (- 5 (strlen newcod)) (setq newcod (strcat "0" newcod)))
		   (setq n_base (substr (car (last tabrinfor)) 1 5))
                   (setq rig-p (strcat "\"" n_base newcod "\"\t\"Rinforzo pannello\"\t\"" (NTH 1 RIG_p)"\"\t" (rtos (NTH 2 RIG_p) 2 1) "\t\"Nr\""))
                   (SETQ nomerin (strcat n_base newcod))
                   (IF REGP (SETQ RIG_A-p (strcat nomerin "|Rinforzo pannello|Nr.|" (rtos (nth 2 rig_p) 2 1) "|||Rinforzo|||||0|0||||"))
		     (SETQ RIG_A-p (strcat nomerin "|Rinforzo pannello|Nr.|" (rtos (nth 2 rig_p) 2 1) "|||Rinforzo|||||"))
		     )
                   (if go! (write-line rig-p file))
                   (s_close file (strcat modalita "tabrinf.txt"))
                   (setq TABRINFor (carica "tabrinf" modalita))
                   (setq TABRINfo $tb$)
                   (if go! (progn (write-line rig_A-p filea); (inquad rig_A-p)
			     ))
                   (setq file (S_OPEN (strcat modalita "DIBrin.txt") "a"))
                   (setq rig (strcat "\"" nomerin "\"\t\"" (NTH 1 rig_p) "\"\t" (rtos (nth 2 rig_p) 2 1)))
                   (if go! (write-line rig file))
                   (s_close file (strcat modalita "DIBrin.txt"))
	            (SETQ RIG_A (STRCAT NOMErin "|" (NTH 1 rig_P) "|" (RTOS (/ (atof (rtos (NTH 2 rig_P))) 1000) 2 2) "||"))
		     (SETQ RIG_A6 (STRCAT NOMErin "|" (NTH 1 rig_P) "|" (RTOS (/ (atof (rtos (NTH 2 rig_P))) 1000) 2 2) "||||"))
	
                   (if go! (WRITE-LINE RIG_A FILED))
		  (if go! (WRITE-LINE RIG_A6 FILED6))
                )
             )
             (setq LISTAPs (cons (list NOMERIN 1 (atoi (rtos XRIN 2 0)) (atoi (rtos (nth 3 bl_rin) 2 0)) 0 0) LISTAPs))
	    
    	    (SETQ NRF (+ 1 NRF))
  	  )         
       )
       (SETQ rinfsn "No")
     )
;FINE RINFORZI    
     (setq listapl nil)
     (setq lrig (list (strcat "Sviluppo Pannello " (nth 2 (assoc finit fogl))) (atof (rtos lunglam 2 1)) (atoi (rtos spes 2 0)) (atoi (rtos halt_F 2 0)) finit forisn "_" (atoi (rtos (length listap) 2 0)) MODOP "Nr"))
     (setq newpan nil)
     (SETQ LIS1 NIL)
     (FOREACH PANDL sviluppi
        (IF (equal (CDR PANDL) LRIG)
          (SETQ LIS1 (CONS PANDL LIS1))
        )
     )
;sviluppi
    (IF (NULL LIS1) (SETQ NEWPAN "T"))
    (SETQ LIS LIS1)
    (if (AND LISTAP (null newPAN))
      (progn
	(SETQ LIS LIS1)
	(FOREACH PN LISTAP;sono solo fori
          (SETQ LISZ NIL)
	  (FOREACH N LIS  
	    (SETQ PK (CONS (CAR N) (cons (car pn) (cons (atoi (rtos halt_F 2 0)) (cons finit (cons forisn (cdr PN)))))))
	    (IF (MEMBER PK dibsvi) (PROGN  (SETQ LISZ (CONS N LISZ))))
	    (SETQ LIS LISZ)
	  )
	)
      )
    )
    (IF LIS (SETQ NEWPAN NIL NOMEPAN (CAR (LAST LIS))) (SETQ NEWPAN "T"))
    (if newPAN
       (progn
	 (setq newcod (rtos (+ 1 (atoi (substr (car (last sviluppi)) 6))) 2 0))
	 (repeat (- 5 (strlen newcod)) (setq newcod (strcat "0" newcod)))
	 (setq file (S_OPEN (strcat modalita "sviluppi.txt") "a"))
	 (if (findfile (strcat modalita "$$sviluppi.txt")) (setq filet (S_OPEN (strcat modalita "$$sviluppi.txt") "a")) (setq filet nil))
	 (setq n_base (substr (car (last sviluppi)) 1 5))
	 (if (= "Si" forisn) (setq dessvi "SvilFor") (setq dessvi "SvilnonFor"))
	 (setq rig (strcat "\""n_base newcod "\"\t\"Sviluppo Pannello " (nth 2 (assoc finit fogl)) "\"\t" (rtos lunglam 2 1) "\t" (rtos spes 2 0) "\t"
			   (rtos halt_F 2 0) "\t\"" finit "\"\t\"" forisn "\"\t\"_\"\t" (rtos (length listap) 2 0) "\t\"" MODOP "\"\t\"Nr\""
			   )
	       nomepan (strcat n_base newcod))
	 (IF REGP (SETQ RIG_A (strcat nomepan "|Sviluppo Pannello " (nth 2 (assoc finit fogl)) "|Nr.|" (rtos lunglam 2 1) "|"  "|"(rtos halt_F 2 0)
			     "|" dessvi "|" MODOP "|" finit "||" nomepan ".00|0|0||||"
			   )
	       )
	   (SETQ RIG_A (strcat nomepan "|Sviluppo Pannello " (nth 2 (assoc finit fogl)) "|Nr.|" (rtos lunglam 2 1) "|"  "|"(rtos halt_F 2 0)
			     "|" dessvi "|" MODOP "|" finit "||" nomepan ".00|"
			   )
	       )
	 )
 	 (setq $sviluppi (cons nomepan $sviluppi))

         (if go! (write-line rig file))
	 (if (and go! filet) (write-line rig filet))
         (s_close file (strcat modalita "sviluppi.txt"))
	 (if filet (s_close filet (strcat modalita "$$sviluppi.txt")))
	 
         (setq sviluppi (carica_f "sviluppi" modalita))
         (setq svilupp $tb$)
         (if go! (progn (write-line rig_A filea) ;(inquad rig_A)
		   ))
         (setq file (S_OPEN (strcat modalita "dibsvi.txt") "a"))
         (if (findfile (strcat modalita "$$dibsvi.txt")) (setq filet (S_OPEN (strcat modalita "$$dibsvi.txt") "a")) (setq filet nil))
	 
 	 (foreach n LISTAP
           (setq rig (strcat "\"" nomePAN "\"\t\""(NTH 0 N) "\"\t" (rtos halt_f 2 0) "\t\"" finit "\"\t\"" forisn
			     "\"\t" (rtos (NTH 1 N) 2 1) "\t" (RTOS (NTH 2 N) 2 1)
                              "\t" (RTOS (NTH 3 N) 2 0) "\t" (RTOS (NTH 4 N) 2 1) "\t" (RTOS (NTH 5 N) 2 1)));massimofori
           (if go! (write-line rig file))
	   (if (and go! filet) (write-line rig filet))
	   (SETQ RIG_A (STRCAT NOMEPAN "|" (NTH 0 N) "|" (RTOS (NTH 3 N) 2 0) "||"))
	 
	   (IF (/= "000000000" (NTH 0 N)) (progn
					    (if go! (WRITE-LINE RIG_A FILED))
					    (if go! (WRITE-LINE RIG_A6 FILED6))))
	 )
	 
         (s_close file (strcat modalita "dibsvi.txt"))
	 (if filet (s_close filet (strcat modalita "$$dibsvi.txt")))
         (setq dibsvi (carica_f "dibsvi" modalita))
         (setq dibsv $tb$)
       )
    )
    (setq nomesvi nomepan)
;pannello-------------------------------------------------------------------------------------------------------------
    (setq listapx listap)
    (setq listap nil)

    (foreach n listapx
      	   (IF (= "000000000" (NTH 0 N))
	     (setq listap (cons n listap))
	     (setq listap (cons (subst nomepan (car n) n) listap))
	   )
    )
     (if (= lung2 0)
         (setq lrig (list "Pannello" (atoF (rtos lung 2 1)) (atoF (rtos lung2 2 1)) (atoi (rtos spes 2 0)) (atoi (rtos halt 2 0)) (atoi (rtos angpan 2 0)) finit forisn "_" (atoi (rtos (length listap) 2 0)) MODOP "Nr")); angpan1 angpan2))
         (setq lrig (list "Angolo" (atoF (rtos lung 2 1)) (atoF (rtos lung2 2 1)) (atoi (rtos spes 2 0)) (atoi (rtos halt 2 0)) (atoi (rtos angpan 2 0)) finit forisn "_" (atoi (rtos (length listap) 2 0)) MODOP "Nr"));;  angpan1 angpan2))
     )
     (setq newpan nil)
     (SETQ LIS1 NIL)
     (FOREACH PANDL LISPAN
        (IF (equal (CDR PANDL) LRIG)
          (SETQ LIS1 (CONS PANDL LIS1))
        )
     )
     (IF (NULL LIS1) (SETQ NEWPAN "T"))
     (SETQ LIS LIS1)
    
    (if (AND LISTAP (null newPAN))
      (progn
        ;(alert "pp")
	(SETQ LIS LIS1)
	(FOREACH PN LISTAP;sono solo fori
          (SETQ LISZ NIL)
	  (FOREACH N LIS  
;;;	    (SETQ PK (CONS (CAR N) PN))
	    (SETQ PK (CONS (CAR N) (cons (car pn) (cons (atoi (rtos halt_F 2 0)) (cons finit (cons forisn (cdr PN)))))))
	    (IF (MEMBER PK DIBPAN) (PROGN  (SETQ LISZ (CONS N LISZ))))
	    (SETQ LIS LISZ)
	  )
	)
      )
    )
    (setq newcod (rtos (+ 1 (atoi (substr (car (last lispan)) 6))) 2 0))
	(repeat (- 5 (strlen newcod)) (setq newcod (strcat "0" newcod)))
	(setq n_base (substr (car (last lispan)) 1 5))
        (setq nomepan (strcat n_base newcod))

    (IF LIS (SETQ NEWPAN NIL NOMEPAN (CAR (LAST LIS))) (SETQ NEWPAN "T"))
    (if lis (prompt (strcat "\nIl Pannello In Lamiera eiste già e si chiama " (setq lamnome (car (last lis)))))
      (prompt (strcat "\nIl Pannello In Lamiera E' NUOVO e si chiama " (setq lamnome NOMEPAN)))
    )
    (setq bl_newnomel (getstring"\nDigitare il nuovo nome o invio per confermare :"))
    (if (assoc bl_newnomel lispan) (progn (alert "\nEsiste gia un pannello con questo nome !!") (exit)))

    (if (and newPAN (= "" bl_newnomel))
       (progn
	 (setq newcod (rtos (+ 1 (atoi (substr (car (last lispan)) 6))) 2 0))
	 (repeat (- 5 (strlen newcod)) (setq newcod (strcat "0" newcod)))
	 (setq file (S_OPEN (strcat modalita "pannellil.txt") "a"))
	 (if (findfile (strcat modalita "$$pannellil.txt")) (setq filet (S_OPEN (strcat modalita "$$pannellil.txt") "a")) (setq filet nil))
	 (setq n_base (substr (car (last lispan)) 1 5))
         
	 (if (= lung2 0)
	   (PROGN
             (setq rig (strcat "\""n_base newcod "\"\t\"Pannello\"\t" (rtos lung 2 1) "\t" (rtos lung2 2 1) "\t" (rtos spes 2 0) "\t"
	                  (rtos halt 2 0) "\t" (rtos angpan 2 0) "\t\"" finit "\"\t\"" forisn "\"\t\"_\"\t" (rtos (length listap) 2 0) "\t\"" MODOP "\"\t\"Nr\""
	               )
		   
	           nomepan (strcat n_base newcod))
	     (IF REGP (SETQ RIG_A (strcat nomepan "|Pannello Dritto  |Nr.|" (rtos lung 2 1) "|" (rtos lung2 2 1) "|"(rtos halt 2 0)
                           "|PanLamiera|" MODOP "|" finit "||" nomepan ".00|0|0||||"
                         )		   
	     )
	       (SETQ RIG_A (strcat nomepan "|Pannello Dritto  |Nr.|" (rtos lung 2 1) "|" (rtos lung2 2 1) "|"(rtos halt 2 0)
                           "|PanLamiera|" MODOP "|" finit "||" nomepan ".00|"
                         )		   
	     )
	       )
	   )
	   (PROGN
             (setq rig (strcat "\"" n_base newcod "\"\t\"Angolo\"\t" (rtos lung 2 1) "\t" (rtos lung2 2 1) "\t" (rtos spes 2 0) "\t"
	                  (rtos halt 2 0) "\t" (rtos angpan 2 0) "\t\"" finit "\"\t\"" forisn "\"\t\"_\"\t" (rtos (length listap) 2 0) "\t\"" MODOP "\"\t\"Nr\""
	               )
	           nomepan (strcat n_base newcod))
	   (IF REGP (SETQ  rig_a (strcat nomepan "|Pannello piegato |Nr.|" (rtos lung 2 1) "|" (rtos lung2 2 1) "|"(rtos halt 2 0)
		            "|AngLamiera|" MODOP "|" finit "||" nomepan ".00|0|0||||" ;00
                         )		   
             )
	     (SETQ  rig_a (strcat nomepan "|Pannello piegato |Nr.|" (rtos lung 2 1) "|" (rtos lung2 2 1) "|"(rtos halt 2 0)
		            "|AngLamiera|" MODOP "|" finit "||" nomepan ".00|" ;00
                         )		   
             )
	     )
	   )
	 )
 	 (setq $pannellil (cons nomepan $pannellil))
         (if go! (write-line rig file))
	 (if (and go! filet) (write-line rig filet))
         (s_close file (strcat modalita "pannellil.txt"))
	 (if filet (s_close filet (strcat modalita "$$pannellil.txt")))
         (setq lispan (carica_f "pannellil" modalita))
	 
         (setq lispn $tb$)
         (if go! (progn (write-line rig_A filea) ;(inquad rig_A)
		   ))
         (setq file (S_OPEN (strcat modalita "DIBpan.txt") "a"))
	 (if (findfile (strcat modalita "$$DIBpan.txt")) (setq filet (S_OPEN (strcat modalita "$$DIBpan.txt") "a")) (setq filet nil))
 	 (foreach n LISTAP
	   (setq rig (strcat "\"" nomePAN "\"\t\""(NTH 0 N) "\"\t" (rtos halt 2 0) "\t\"" finit "\"\t\"" forisn
			     "\"\t" (rtos (NTH 1 N) 2 1) "\t" (RTOS (NTH 2 N) 2 1)
                              "\t" (RTOS (NTH 3 N) 2 0) "\t" (RTOS (NTH 4 N) 2 1) "\t" (RTOS (NTH 5 N) 2 1)))
           (if go! (write-line rig file))
	   (if (and go! filet) (write-line rig filet))
	   (SETQ RIG_A (STRCAT NOMEPAN "|" (NTH 0 N) "|" (RTOS (NTH 3 N) 2 0) "||"))
	     (SETQ RIG_A6 (STRCAT NOMEPAN "|" (NTH 0 N) "|" (RTOS (NTH 3 N) 2 0) "||||"))
	 
	   (IF (/= "000000000" (NTH 0 N)) (progn (if go!  (WRITE-LINE RIG_A FILED))(if go! (WRITE-LINE RIG_A6 FILED6))))
	 )
         (s_close file (strcat modalita "DIBpan.txt"))
         (if filet (s_close filet (strcat modalita "$$DIBpan.txt")))
	 
         (setq DIBpan (carica_f "DIBpan" modalita))
         (setq DIBpn $tb$)
       )
    )

    
(if (/= "" bl_newnomel)
       (progn
         (setq nomepan bl_newnomel)         
	 (if (= lung2 0)
	   (PROGN
             (setq rig (strcat "\"" nomepan "\"\t\"" desc-pan "\"\t" (rtos lung 2 1) "\t" (rtos lung2 2 1) "\t" (rtos spes 2 0) "\t"
	                  (rtos halt 2 0) "\t" (rtos angpan 2 0) "\t\"" finit "\"\t\"" forisn "\"\t\"_\"\t" (rtos (length listap) 2 0) "\t\"" MODOP "\"\t\"NR\""
	               )
	     )
	     (IF REGP (SETQ RIG_A (strcat nomepan "|" desc-pan "|Nr.|" (rtos lung 2 1) "|" (rtos lung2 2 1) "|"(rtos halt 2 0)
                           "|PanLamiera|" MODOP "|" finit "||" nomepan ".00|0|0||||"
                         )		   
	     )
	       (SETQ RIG_A (strcat nomepan "|" desc-pan "|Nr.|" (rtos lung 2 1) "|" (rtos lung2 2 1) "|"(rtos halt 2 0)
                           "|PanLamiera|" MODOP "|" finit "||" nomepan ".00|"
                         )		   
	     )
	       )
	   )
	   (PROGN
             (setq rig (strcat "\"" nomepan "\"\t\"" desc-pan "\"\t" (rtos lung 2 1) "\t" (rtos lung2 2 1) "\t" (rtos spes 2 0) "\t"
	                  (rtos halt 2 0) "\t" (rtos angpan 2 0) "\t\"" finit "\"\t\"" forisn "\"\t\"_\"\t" (rtos (length listap) 2 0) "\t\"" MODOP "\"\t\"Nr\""
	               )
	     )
	   (IF REGP (SETQ  rig_a (strcat nomepan "|" desc-pan "|Nr.|" (rtos lung 2 1) "|" (rtos lung2 2 1) "|"(rtos halt 2 0)
		            "|AngLamiera|" MODOP "|" finit "||" nomepan ".00|0|0||||" ;00
                         )		   
             )
	     (SETQ  rig_a (strcat nomepan "|" desc-pan "|Nr.|" (rtos lung 2 1) "|" (rtos lung2 2 1) "|"(rtos halt 2 0)
		            "|AngLamiera|" MODOP "|" finit "||" nomepan ".00|" ;00
                         )		   
             )
	     )
	   )
	 )
 	 (setq $pannellil (cons nomepan $pannellil))
     	(setq file (S_OPEN (strcat modalita "pannellil.txt") "a"))
	(CLOSE file)
	(SETQ FILE- (OPEN (strcat modalita "pannellil.tx_") "r"))
	(SETQ FILE+ (OPEN (strcat modalita "pannellil.txt") "w"))
	(write-line (read-line file-) file+)
	(write-line (read-line file-) file+)
	(write-line rig file+)
	(while (setq rg (read-line file-))
	  (write-line rg file+)
	)
	(close file+)
	(close file-)
	(vl-file-delete (strcat modalita "pannellil.tx_"))
	 
         (setq lispan (carica_f "pannellil" modalita))
         (setq lispn $tb$)
         (if go! (progn (write-line rig_A filea) ;(inquad rig_A)
		   ))

	 
         (setq file (S_OPEN (strcat modalita "DIBpan.txt") "a"))
	 (if (findfile (strcat modalita "$$DIBpan.txt")) (setq filet (S_OPEN (strcat modalita "$$DIBpan.txt") "a")) (setq filet nil))
 	 (foreach n LISTAP
	   (setq rig_& (strcat "\"" nomePAN "\"\t\""(NTH 0 N) "\"\t" (rtos halt 2 0) "\t\"" finit "\"\t\"" forisn
			     "\"\t" (rtos (NTH 1 N) 2 1) "\t" (RTOS (NTH 2 N) 2 1)
                              "\t" (RTOS (NTH 3 N) 2 0) "\t" (RTOS (NTH 4 N) 2 1) "\t" (RTOS (NTH 5 N) 2 1)))
           (if go! (write-line rig file))
	   (if (and go! filet) (write-line rig filet))
           (SETQ RIG_A (STRCAT NOMEPAN "|" (NTH 0 N) "|" (RTOS (NTH 3 N) 2 0) "||"))

	   (IF (/= "000000000" (NTH 0 N)) (progn (if go!  (WRITE-LINE RIG_A FILED))(if go! (WRITE-LINE RIG_A6 FILED6))))
	 )
         (s_close file (strcat modalita "DIBpan.txt"))
         (if filet (s_close filet (strcat modalita "$$DIBpan.txt")))
         (setq DIBpan (carica_f "DIBpan" modalita))
         (setq DIBpn $tb$)
       )
    )

;assieme pannelllo





;    integ01
;;;;;;;;;;;;;;;;;;;;;;;;
    (SETQ LIS NIL)
    (SETQ LIS1 NIL)
    (setq resisor resis)
    (IF (AND (= RESIS "B15") (= FORISN "Si")) (PROGN  (SETQ RESIS "B0")))
    (IF (= RESIS "B0+") (PROGN (SETQ RESIS "B15")))
    (If (and (= FORISN "Si"))
      (progn
	(SETQ ALTKIT halt)
	(setq listk nil)
	(setq pt '(0 0 0))
	(setq pt0x_f pt)
	(setq ldpos0_f lung)
	(DIBFORO_ag)
	
	(foreach k listk (setq listaps (cons (list (nth 0 k)
						   (nth 2 k)
						   (nth 1 k)
						   (nth 3 k)
						   (nth 4 k)
						   (nth 5 k)
					     )
						   listaps)))
	
      )
    )
;lanacer
    

;mater
    (if (= resis "B0")
        (setq deskldr "Foglio lana di roccia Sp. 15" spmnan 15)
        (setq deskldr "Foglio lana di roccia Sp. 25" spmnan 25)
    )
  (if (/= resis  "B0") (setq resisk "B15") (setq resisk "B0"))
    (if (= modop "MAN")
        (setq len_m (member (list resis 0) lanadi))
        (setq len_m (member (list resisk (atoi (rtos halt 2 0))) lanadi))
    )
    (if (null len_m) (setq len_m (member (list resis 0) lanadi)))
    (if (null len_m) (progn (alert "Riga mancante in lanadir.txt!!") (exit)))
    (setq cod_m (car (nth (- (LENGTH LANADI) (length len_m)) lanadir)))
    (IF (/= (RTOS LUNG2 2 0) "0")
      (if (< 180 angpan)
	  (if (< lung lung2)
	    (SETQ LLUNG_M (LIST (- LUNG (/ (cadr (assoc 'diflungldr parametri)) 2))
                                (- LUNG2 spmnan (/ (cadr (assoc 'diflungldr parametri))2)))
            )
	    (SETQ LLUNG_M (LIST (- LUNG2 (/ (cadr (assoc 'diflungldr parametri)) 2))
                                (- LUNG spmnan (/ (cadr (assoc 'diflungldr parametri))2)))
            )
	  )
	  (if (< lung lung2)
	    (SETQ LLUNG_M (LIST (+ spmnan (- LUNG (/ (cadr (assoc 'diflungldr parametri)) 2)))
                                (- LUNG2 (/ (cadr (assoc 'diflungldr parametri))2)))
            )
	    (SETQ LLUNG_M (LIST (- LUNG (/ (cadr (assoc 'diflungldr parametri))2))
				(+ spmnan (- LUNG2 (/ (cadr (assoc 'diflungldr parametri)) 2)))
                          )
            )
	  )
       )
       (SETQ LLUNG_M (LIST (- LUNG (cadr (assoc 'diflungldr parametri)))))
    )
    (FOREACH LUNG_M LLUNG_M
      (setq rig_m (list deskldr cod_m (atof (rtos lung_M 2 1)) (atoi (rtos (- halt (cadr (assoc 'diffaltldr parametri))) 2 0))
			0 (atoi (rtos (* (atof (rtos lung_M 2 1))
				         (atof (rtos (- halt (cadr (assoc 'diffaltldr parametri))) 2 1))) 2 0)) "Nr" ))
;(atof (rtos      
      (if (setq percod_m (member rig_m mate))
	(setq NOMEPAN_m (car (nth (- (LENGTH MATE) (length percod_m)) mater)))
	(progn
	  (setq file (S_OPEN (strcat modalita "mater.txt") "a"))
	  (setq newcod (rtos (+ 1 (atoi (substr (car (last mater)) 6))) 2 0))
	  (repeat (- 5 (strlen newcod)) (setq newcod (strcat "0" newcod)))
	  (setq n_base (substr (car (last mater)) 1 5))
	  (setq rig-m (strcat "\""n_base newcod "\"\t\"" deskldr "\"\t\"" (NTH 1 RIG_m)"\"\t" (rtos (NTH 2 RIG_m) 2 1)
			      "\t" (rtos (NTH 3 RIG_m)2 0) "\t" (RTOS (NTH 4 RIG_m) 2 0) "\t" (rtos (NTH 5 RIG_m) 2 0)
			      "\t\"" (NTH 6 RIG_m) "\"")
		)
	  (SETQ nomepan_m (strcat n_base newcod))
  	  (if (= resis "B0+") (setq resis "B15"))
	  (if (= resis "B15+") (setq resis "B15"))

	  (IF REGP (SETQ RIG_A-m (strcat nomepan_m "|" deskldr "|Nr.|" (rtos (nth 2 rig_m) 2 1) "|" (rtos (nth 3 rig_m) 2 1) "|"(rtos (nth 4 rig_m) 2 0)
				"|materassino|" "|" resis "|" "|" "|0|0||||"
				)
		)
	    (SETQ RIG_A-m (strcat nomepan_m "|" deskldr "|Nr.|" (rtos (nth 2 rig_m) 2 1) "|" (rtos (nth 3 rig_m) 2 1) "|"(rtos (nth 4 rig_m) 2 0)
				"|materassino|" "|" resis "|" "|" "|"
				)
		)
	  )
	  (if go! (write-line rig-m file))
	  (s_close file (strcat modalita "mater.txt"))
	  (setq mater (carica "mater" modalita))
	  (setq mate $tb$)
	  (if go! (progn (write-line rig_A-m filea) ;(inquad rig_A-m)
		    ))
	  (setq file (S_OPEN (strcat modalita "DIBldr.txt") "a"))
	  (setq rig (strcat "\"" nomePAN_m "\"\t\"" (NTH 1 rig_m) "\"\t" (RTOS (NTH 2 rig_m) 2 0)
			    "\t" (RTOS (NTH 3 rig_m) 2 0) "\t" (RTOS (NTH 4 rig_m) 2 0) "\t" (RTOS (NTH 5 rig_m) 2 0)))
	  (if go! (write-line rig file))
	  (SETQ RIG_A (STRCAT NOMEPAN_m "|" (NTH 1 rig_m) "|" (RTOS (/ (atof (rtos (NTH 5 rig_m))) 1000000) 2 2) "||"))
	
	  (if go! (WRITE-LINE RIG_A FILED))
	  (s_close file (strcat modalita "DIBldr.txt"))
	  )
	)
      (setq listaps (cons (list nomepan_m 1 0 0 0 0) listaps))
   )
        (cond ((and (= resisor "B15+") (= "Si" forisn)) (setq desctec "SRS 30 256 B15"))
          ((and (= resisor "B15") (= "Si" forisn)) (setq desctec "SRS 30 156 B15"))
          ((and (= resisor "B0+") (= "Si" forisn))  (setq desctec "SRS 30 25 B0"))
	  ((and (= resisor "B0+") (= "No" forisn))  (setq desctec "SRS 30 25 B15"))
          ((and (or (= resisor "B15") (= resisor "B15+")) (= "No" forisn)) (setq desctec "SRS 30 25 B15"))
          (t (setq desctec "SRS 30 15 B0"))
    )
    (if (and (= resisor "B0+") (= "No" forisn)) (setq resis "B15"))
    (if (and (= resisor "B0+") (= "Si" forisn)) (setq resis "B0"))
    (if (= resis "B15+") (setq resis "B15"))
    (setq lrigs (list nomepan "Assieme pannello" resis "Nr" (atoi (rtos (length listaps) 2 0)) desctec finit (atoi (rtos halt)) forisn))
    (setq newpas nil)
    (FOREACH PANDL LISPAs
        (IF (equal (CDR PANDL) LRIGs)
          (SETQ LIS1 (CONS PANDL LIS1))
        )
     )
     (IF (NULL LIS1) (SETQ NEWPAs "T"))
     (SETQ LIS LIS1)
    
    (if (AND LISTAPs (null newPAs))
      (progn
	(SETQ LIS LIS1)
	(FOREACH Ps LISTAPs
          (SETQ LISZ NIL)
	  (FOREACH N LIS
;;;	    (SETQ PK (CONS (CAR N) Ps))
	    (SETQ PK (CONS (CAR N) (cons (car ps) (cons (atoi (rtos halt_F 2 0)) (cons finit (cons forisn (cdr Ps)))))))
	    (IF (MEMBER PK DIBPAs) (PROGN  (SETQ LISZ (CONS N LISZ))))
	    (SETQ LIS LISZ)
	  )
	)
      )
    )
    (IF LIS (SETQ NEWPAs NIL NOMEPAns (CAR (LAST LIS))) (SETQ NEWPAs "T"))
        (setq newcodx (rtos (+ 1 (atoi (substr (car (last lispas)) 6))) 2 0))
	(repeat (- 5 (strlen newcodx)) (setq newcodx (strcat "0" newcodx)))
	(setq n_base (substr (car (last lispas)) 1 5))
        (setq nomepans (strcat n_base newcodx))

    (if lis (prompt (strcat "\nIl Pannello eiste già e si chiama " (setq nomepans (setq disnome (car (last lis))))))
      (prompt (strcat "\nIl Pannello E' NUOVO e si chiama " (setq disnome nomepans)))
    )
  
    (setq bl_newnome (getstring"\nDigitare il nuovo nome o invio per confermare :"))
    (if (assoc bl_newnome lispas) (progn (alert "\nEsiste gia un pannello con questo nome !!") (exit)))
    (if (and newPAs (= "" bl_newnome))
      (progn
        (setq newcodx (rtos (+ 1 (atoi (substr (car (last lispas)) 6))) 2 0))
	(repeat (- 5 (strlen newcodx)) (setq newcodx (strcat "0" newcodx)))
	(setq n_base (substr (car (last lispas)) 1 5))
	(setq rig (strcat "\"" n_base newcodx "\"\t\"" nomepan "\"\t\"Assieme pannello\"\t\"" resis "\"\t\"Nr\"\t"(rtos (length listaps) 2 0)"\t\"" desctec "\"\t\"" finit "\"\t" (rtos halt 2 0) "\t\"" forisn "\""))
	(setq $pannelli (cons (strcat n_base newcodx) $pannelli))
        (setq nomepans (strcat n_base newcodx))
     	(setq file (S_OPEN (strcat modalita "pannelli.txt") "a"))
	(if (findfile (strcat modalita "$$pannelli.txt")) (setq filet (S_OPEN (strcat modalita "$$pannelli.txt") "a")) (setq filet nil))
        (if go! (write-line rig file))
	(if (and go! filet) (write-line rig filet))
        (s_close file (strcat modalita "pannelli.txt"))
        (if filet (s_close filet (strcat modalita "$$pannelli.txt")))
        (setq lispas (carica_f "pannelli" modalita))
        (setq lisps $tb$)
	(pesopan (strcat n_base newcodx))
	(setq file (S_OPEN (strcat modalita "DIBpaS.txt") "a"))
	(if (findfile (strcat modalita "$$DIBpaS.txt")) (setq filet (S_OPEN (strcat modalita "$$DIBpaS.txt") "a")) (setq filet nil))
        (if go! (write-line  (strcat "\"" n_base newcodx "\"\t\"" nomepan "\"\t" (rtos halt 2 0) "\t\"" finit "\"\t\"" forisn "\"\t1") file))
	(if (and go! filet) (write-line (strcat "\"" n_base newcodx "\"\t\"" nomepan "\"\t" (rtos halt 2 0) "\t\"" finit "\"\t\"" forisn "\"\t1") filet))
        (IF REGP (setq rig_a (strcat n_base newcodx "|Assieme pannello|Nr.|0|0|0|Pannello|" resis "|" desctec "||" NBASEPAS newcodx".00|" (rtos mqpan 2 2)"|" (rtos pesop 2 2)"||||" )) ;calcolopeso
	  (setq rig_a (strcat n_base newcodx "|Assieme pannello|Nr.|0|0|0|Pannello|" resis "|" desctec "||" NBASEPAS newcodx".00|"))
	  )
	(if go! (progn (write-line rig_a filea) ;(inquad rig_A)
		  ))
        (if go! (write-line  (strcat n_base newcodx "|" nomepan "|1||") filed))
	
	(foreach db listaps
           (setq rig (strcat "\"" n_base newcodx "\"\t\"" (NTH 0 db) "\"\t" (rtos halt 2 0) "\t\"" finit "\"\t\"" forisn
			     "\"\t" (rtos (NTH 1 db) 2 1) "\t" (RTOS (NTH 2 db) 2 1)
                              "\t" (RTOS (NTH 3 db) 2 1) "\t" (RTOS (NTH 4 db) 2 1) "\t" (RTOS (NTH 5 db) 2 1)))
	   (if (member (nth 0 db) (cdr (assoc 'tubiinkit parametri)))
	     (setq rig_a (strcat n_base newcodx "|" (NTH 0 db) "|" (rtos (/ (NTH 1 db) 1000.0) 2 2) "||"))
             (if (= (nth 0 db) selvelovetro)
		   (If (= "6RP" (substr (NTH 0 db) 3 3))
		     (setq rig_a6 (strcat n_base newcodx "|" (NTH 0 db) "|" (rtos (/ (NTH 1 db) 1000000.0) 2 2) "||" (rtos (NTH 2 db) 2 2) "|" (rtos (NTH 3 db) 2 2) "|")
			   rig_a (strcat n_base newcodx "|" (NTH 0 db) "|" (rtos (/ (NTH 1 db) 1000000.0) 2 2) "||"));delta
                     (setq rig_a6 (strcat n_base newcodx "|" (NTH 0 db) "|" (rtos (/ (NTH 1 db) 1000000.0) 2 2) "||||")
			    rig_a (strcat n_base newcodx "|" (NTH 0 db) "|" (rtos (/ (NTH 1 db) 1000000.0) 2 2) "||")
			   )
		     )
		   (If (= "6RP" (substr (NTH 0 db) 3 3))
		     (setq rig_a6 (strcat n_base newcodx "|" (NTH 0 db) "|" (rtos (NTH 1 db) 2 1) "||" (rtos (NTH 2 db) 2 2) "|" (rtos (NTH 3 db) 2 2) "|")
			   rig_a (strcat n_base newcodx "|" (NTH 0 db) "|" (rtos (NTH 1 db) 2 1) "||"));delta
		     (setq rig_a6 (strcat n_base newcodx "|" (NTH 0 db) "|" (rtos (NTH 1 db) 2 1) "||||")
			   rig_a (strcat n_base newcodx "|" (NTH 0 db) "|" (rtos (NTH 1 db) 2 1) "||"))
		     )
		   ;)
	     )
	   )
	   (if go! (write-line rig_a filed))
           (if go! (write-line rig file))
	  (if (and go! filet) (write-line rig filet))
	  
        )
        (s_close file (strcat modalita "DIBpaS.txt"))
        (if filet (s_close filet (strcat modalita "$$DIBpaS.txt")))
        (setq DIBpas (carica_f "DIBpas" modalita))
        (setq DIBps $tb$)
      )	
    )
(if (/= "" bl_newnome)
      (progn
	(setq rig (strcat "\"" bl_newnome "\"\t\"" nomepan "\"\t\"Assieme pannello\"\t\"" resis "\"\t\"Nr\"\t"(rtos (length listaps) 2 0)"\t\"" desctec "\"\t\"" finit "\"\t" (rtos halt 2 0) "\t\"" forisn "\""))
	(setq $pannelli (cons (strcat n_base newcodx) $pannelli))
        (setq nomepans bl_newnome)
     	(setq file (S_OPEN (strcat modalita "pannelli.txt") "a"))
	(CLOSE file)
	(SETQ FILE- (OPEN (strcat modalita "pannelli.tx_") "r"))
	(SETQ FILE+ (OPEN (strcat modalita "pannelli.txt") "w"))
	(write-line (read-line file-) file+)
	(write-line (read-line file-) file+)
	(write-line rig file+)
	(while (setq rg (read-line file-))
	  (write-line rg file+)
	)
	(close file+)
	(close file-)
	(vl-file-delete (strcat modalita "pannelli.tx_"))
        (setq lispas (carica_f "pannelli" modalita))
        (setq lisps $tb$)
	(pesopan (strcat bl_newnome))
	(setq file (S_OPEN (strcat modalita "DIBpaS.txt") "a"))
	(if (findfile (strcat modalita "$$DIBpaS.txt")) (setq filet (S_OPEN (strcat modalita "$$DIBpaS.txt") "a")) (setq filet nil))
        (if go! (write-line  (strcat "\"" n_base newcodx "\"\t\"" nomepan "\"\t" (rtos halt 2 0) "\t\"" finit "\"\t\"" forisn "\"\t1") file))
	(if (and go! filet) (write-line (strcat "\"" n_base newcodx "\"\t\"" nomepan "\"\t" (rtos halt 2 0) "\t\"" finit "\"\t\"" forisn "\"\t1") filet))
	
        (IF REGP (setq rig_a (strcat bl_newnome "|" desc-pas "|Nr.|0|0|0|Pannello|" resis "|" desctec "||" NBASEPAS newcodx".00|" (rtos mqpan 2 2)"|" (rtos pesop 2 2)"||||" )) ;calcolopeso
	  (setq rig_a (strcat bl_newnome "|" desc-pas "|Nr.|0|0|0|Pannello|" resis "|" desctec "||" NBASEPAS newcodx".00|"))
	  )
	(if go! (progn (write-line rig_a filea) ;(inquad rig_A)
		  ))
        (if go! (write-line  (strcat bl_newnome "|" nomepan "|1||") filed))
	
	(foreach db listaps
           (setq rig (strcat "\"" bl_newnome "\"\t\"" (NTH 0 db) "\"\t" (rtos (NTH 1 db) 2 1) "\t" (RTOS (NTH 2 db) 2 1)
                              "\t" (RTOS (NTH 3 db) 2 1) "\t" (RTOS (NTH 4 db) 2 1) "\t" (RTOS (NTH 5 db) 2 1)))
	   (if (member (nth 0 db) (cdr (assoc 'tubiinkit parametri)))
	     (setq rig_a (strcat bl_newnome "|" (NTH 0 db) "|" (rtos (/ (NTH 1 db) 1000.0) 2 2) "||"))
             (if (= (nth 0 db) selvelovetro)
      	         (IF REGP (setq rig_a (strcat bl_newnome "|" (NTH 0 db) "|" (rtos (/ (NTH 1 db) 1000000.0) 2 2) "||"))
		   (If (= "6RP" (substr (NTH 0 db) 3 3))
		     (setq rig_a (strcat bl_newnome "|" (NTH 0 db) "|" (rtos (/ (NTH 1 db) 1000000.0) 2 2) "||" (rtos (NTH 2 db) 2 2) "|" (rtos (NTH 3 db) 2 2) "|"));delta
		     (setq rig_a (strcat bl_newnome "|" (NTH 0 db) "|" (rtos (/ (NTH 1 db) 1000000.0) 2 2) "||||"))
		     )
		   )
      	         (IF REGP (setq rig_a (strcat bl_newnome "|" (NTH 0 db) "|" (rtos (NTH 1 db) 2 1) "||"))
		   (If (= "6RP" (substr (NTH 0 db) 3 3))
		     (setq rig_a6 (strcat bl_newnome "|" (NTH 0 db) "|" (rtos (NTH 1 db) 2 1) "||" (rtos (NTH 2 db) 2 2) "|" (rtos (NTH 3 db) 2 2) "|")
			   rig_a (strcat bl_newnome "|" (NTH 0 db) "|" (rtos (NTH 1 db) 2 1) "||")
			   );delta
		     (setq rig_a6 (strcat bl_newnome "|" (NTH 0 db) "|" (rtos (NTH 1 db) 2 1) "||||")
			   rig_a (strcat bl_newnome "|" (NTH 0 db) "|" (rtos (NTH 1 db) 2 1) "||")
			   )
		     )
		   )
	     )
	   )
	   (if go! (write-line rig_a filed))
           (if go! (write-line rig file))
	  (if (and go! filet) (write-line rig filet))
        )
        (s_close file (strcat modalita "DIBpaS.txt"))
        (if filet (s_close filet (strcat modalita "$$DIBpaS.txt")))
        (setq DIBpas (carica_f "DIBpas" modalita))
        (setq DIBps $tb$)
      )	
    )
   (if godis (setq pt nil) (setq pt (getpoint "\nPunto di inserimento sigla o invio per non mettere la sigla :")))
   (if (and (null godis) pt)
     (progn
       (setq ang (getangle "\nAngolo sigla <0>:" pt))

       (if (null ang) (setq ang 0))
       (setq codrp "")
       (setq ptn (polar pt (+ ang (/ pi 2)) 200))
       (setq ptna (polar pt (+ ang (/ pi 2)) 100))
       (setq ptns (polar pt (+ ang (/ pi 2)) 0))
       (if ang (setq ang (angtos ang)))

       (command"_layer" "_m" "siglepan" "")
       (command"_insert" "codpas" "_non" ptna "1" "1" ang nomepans codrp)
       (command"_insert" "codpan" "_non" ptn "1" "1" ang nomepan codrp)
       (command"_insert" "codsvi" "_non" ptns "1" "1" ang nomesvi codrp)
    );;;  )
  )
  (command"_layer" "_m" "0" "")
  (if godis
    (progn
      (setvar "tilemode" 1)
      (if (/= "" bl_newnome) (dispas bl_newnome)(dispas disnome))
    )
  )
  (stop)
)

(DEFUN DIBFORO_ag ()
  (SETQ NRF 0)
  (SETQ LISFORP NIL)
  (setq b_lfor nil)
  (setq b_lfor (vl-sort bl_lfor (function (lambda (e1 e2) (> (CADR e1) (CADR e2))))))
  
  (if b_lfor (setq lisforp (cons (list (list (setq foro (list (nth 0 (car b_lfor)) (nth 1 (car b_lfor)))) (nth 2 (car b_lfor)))) lisforp)))
  
  (WHILE (AND b_lfor (> (length b_lfor) 1) (car (SETQ FOROd (list (car (nth (SETQ NRF (+ 1 NRF)) b_lfor))(cadr (nth nrf b_lfor))) )))
    (if (< (abs (- (nth 1 foro) (nth 1 forod))) 30)
      (progn
	(setq lisforp (subst (cons (list forod (nth 2 (nth NRF b_lfor))) (car lisforp))
			    (car lisforp)
			    lisforp
		      )
	)
      )
      (setq lisforp (cons (list (list forod (nth 2 (nth NRF b_lfor)))) lisforp))
    )
    (setq foro forod)
  )
  (setq lisf nil)
  (foreach n lisforp
    (setq n (vl-sort n (function (lambda (e1 e2) (> (CADR e1) (CADR e2))))))
    (setq lisf (cons n lisf))
  )
  (setq lisforp nil)
  (foreach gfori lisf
    (setq pfor (list (cadr (car (car gFORi))) 0 0))
    (if (and (/= ldpos0_f 0) (> (distance pt pfor) ldpos0_f))
      (setq pxdf (+ (distance pt0x_f pfor) ldpos0_f))
      (setq pxdf (distance pt pfor))
    )
    (SETQ LISFORP (CONS (LIST (car (car (car gfori)))
 				   (cadr (car gfori))
				  'NX (atoi (rtos pxdf 2 0))) LISFORP)
    )
    (setq nrxp 0)
    (foreach foro (cdr gfori)
       (setq pfor (list (cadr (car foro)) 0 0))
       (if (and (/= ldpos0_f 0) (> (distance pt pfor) ldpos0_f))
           (setq pxdf (+ (distance pt0x_f pfor) ldpos0_f))
           (setq pxdf (distance pt pfor))
       )
       (if (member (list (SETQ N1 (car (car foro))) (SETQ N2 (car (car (nth nrxp gfori))))) POSpon)
           (SETQ LISFORP (CONS (LIST (car (car foro))
    				          (cadr foro)
				          'SP (atoi (rtos pxdf 2 0))
				          (- (CADR (nth nrxp gfori)) (CADR FORO)
					     (/ (NTH 3 (ASSOC N1 PRESE)) 2)
					     (/ (NTH 3 (ASSOC N2 PRESE)) 2)
			                  )
			       ) LISFORP)

           )
           (if (/= n2 "DFOR0020")
               (SETQ LISFORP (CONS (LIST (car (car foro))
    				          (cadr foro)
				          'SF (atoi (rtos pxdf 2 0))) LISFORP)

               )
               (SETQ LISFORP (CONS (LIST (car (car foro))
    				          (cadr foro)
				          'NX (atoi (rtos pxdf 2 0))) LISFORP)

               )
	   )
       )
       (setq nrxp (+ 1 nrxp))
    )
 )
 (FOREACH FORO LISFORP
    (FOREACH RIGA DISTFORI
      (IF (= (CAR RIGA) (CAR FORO))
        (IF (= 'SP (NTH 2 FORO))
          (COND ((= 'VR (NTH 2 RIGA))
                 (SETQ LISTK (CONS (LIST (NTH 1 RIGA) (NTH 3 foro) (ATOI (RTOS (NTH 4 FORO) 2 0)) (nth 1 foro)
				       (nth 2 (assoc (car foro) prese)) (nth 3 (assoc (car foro) prese))
				 ) LISTK))
                )
                ((member (NTH 1 RIGA) (cdr (assoc 'inninfinkit parametri)))
                 (SETQ LISTK (CONS (LIST (NTH 1 RIGA) (NTH 3 foro) 2 (nth 1 foro)
                                       (nth 2 (assoc (car foro) prese)) (nth 3 (assoc (car foro) prese))				       
				 ) LISTK))
                )
                ((member (NTH 1 RIGA) (cdr (assoc 'scatoleinkit parametri)))
                 (SETQ LISTK (CONS (LIST (NTH 1 RIGA) (NTH 3 foro) 1 (nth 1 foro)
                                       (nth 2 (assoc (car foro) prese)) (nth 3 (assoc (car foro) prese))				       
				 ) LISTK))
                )
          )
          (COND ((= 'VR (NTH 2 RIGA))
                 (SETQ LISTK (CONS (LIST (NTH 1 RIGA) (NTH 3 foro) (ATOI (RTOS (- ALTKIT (NTH 1 FORO)) 2 0)) (nth 1 foro)
				       (nth 2 (assoc (car foro) prese)) (nth 3 (assoc (car foro) prese))
				 ) LISTK))
                )
                ((EQUAL (NTH 2 FORO) (NTH 2 RIGA))
                 (SETQ LISTK (CONS (LIST (NTH 1 RIGA) (NTH 3 foro) 1 (nth 1 foro)
                                       (nth 2 (assoc (car foro) prese)) (nth 3 (assoc (car foro) prese))				       
				 ) LISTK))
                )
                ((= 'INT (TYPE (NTH 2 RIGA))) (SETQ LISTK (CONS (LIST (NTH 1 RIGA) (NTH 3 foro) (NTH 2 RIGA) (nth 1 foro)
								    (nth 2 (assoc (car foro) prese)) (nth 3 (assoc (car foro) prese))
							      ) LISTK)))
          )
	)
      )
    )

  )

)


(defun  verpk (nr) ;inserimento codice pannello
  (setq pnome (get_tile nr))
  (if (null lispas) (setq lispas (carica_f "pannelli" modalita) lisps $tb$))
  (if (null lispan) (setq lispan (carica_f "pannellil" modalita) lispn $tb$))
  (if (null (assoc pnome lispas))
    (progn
     (alert "Pannello insistente in pannelli.txt!!")
     (mode_tile nr 2)
    )
    (progn
       (LEGGINPUTk)
       (setq lp (list pnome (atof (get_tile (strcat "x" nr))) (atof (get_tile (strcat "y" nr)))
		    (nth 2 (assoc (nth 1 (assoc pnome lispas)) lispan))
		    (nth 3 (assoc (nth 1 (assoc pnome lispas)) lispan))))
      (cond ((= "p1" nr) (setq lp1 lp)(mode_tile "ap2" 0))
	    ((= "p2" nr) (setq lp2 lp)(mode_tile "ap3" 0))
	    ((= "p3" nr) (setq lp3 lp)(mode_tile "ap4" 0))
	    ((= "p4" nr) (setq lp4 lp)(mode_tile "ap5" 0))
	    ((= "p5" nr) (setq lp5 lp))
	    )

    )
  )
)
(defun caltra ()
  (setq llt1 nil)
  (setq llt2 nil)
  (setq llt 0)
  (foreach pn lpk
    (setq npan (car pn))
    (if (= 0.0 (nth 4 pn))
      (setq llt (+ llt (nth 3 pn)))
      (progn ;e un angolo
	(setq angolo (nth 6 (assoc (nth 1 (assoc npan lispas)) lispan)))
	(setq llt (+ llt (nth 3 pn)))
	(setq llt1 llt)
	(setq llt (nth 4 pn))
      )
    )
  )
  (if llt1 (setq llt2 llt) (setq llt1 llt))
  (set_tile "ptr1" "30.0")
  (cond ((and llt1 llt2)
	 (set_tile "ltr1" (rtos (- llt1 60) 2 1)) (set_tile "rtr1" "30.0")
	 (set_tile "ltr2" (rtos (- llt2 60) 2 1)) (set_tile "rtr2" "30.0")
	 (set_tile "ptr2" (rtos (+ llt1 30) 2 1))
	)
	(llt1 (set_tile "ltr1" (rtos (- llt1 60) 2 1)) (set_tile "rtr1" "30.0")
	      (set_tile "ltr2" "0") (set_tile "rtr2" "0") (set_tile "ptr2" "0"))
	(llt2 (set_tile "ltr2" (rtos (- llt2 60) 2 1)) (set_tile "rtr2" "30.0")
	      (set_tile "ltr1" "0") (set_tile "rtr1" "0") (set_tile "ptr1" "0"))
  )
      
)
(defun agpkd (nr) ;pressione pulsante aggiungi
  (mode_tile nr 0)
  (mode_tile (strcat "x" nr) 0)
  (mode_tile (strcat "y" nr) 0)
  (set_tile nr "+24PN0")
  (cond ((= "p2" nr)
	 (set_tile (strcat "x" nr) (rtos (+ (nth 3 lp1) (nth 4 lp1)) 2 1)))
	((= "p3" nr)
	 (set_tile (strcat "x" nr) (rtos (+ (nth 3 lp1) (nth 4 lp1) (nth 3 lp2) (nth 4 lp2)) 2 1)))
	((= "p4" nr)
	 (set_tile (strcat "x" nr) (rtos (+ (nth 3 lp1) (nth 4 lp1) (nth 3 lp2) (nth 4 lp2) (nth 3 lp3) (nth 4 lp3)) 2 1)))
	((= "p5" nr)
	 (set_tile (strcat "x" nr) (rtos (+ (nth 3 lp1) (nth 4 lp1) (nth 3 lp2) (nth 4 lp2) (nth 3 lp3) (nth 4 lp3) (nth 3 lp4) (nth 4 lp4)) 2 1)))
  )
)
(defun c:akdia ()
  (setq nrdl (load_dialog "aggpan"))
  (new_dialog "aggkit" nrdl)
  (set_tile "p1" "+24PN0")
  (mode_tile "ap1" 1)
  (mode_tile "p2" 1)
  (mode_tile "p3" 1)
  (mode_tile "p4" 1)
  (mode_tile "p5" 1)
  (action_tile "p1" "(verpk \"p1\")")
  (action_tile "p2" "(verpk \"p2\")")
  (action_tile "p3" "(verpk \"p3\")")
  (action_tile "p4" "(verpk \"p4\")")
  (action_tile "p5" "(verpk \"p5\")")
  (action_tile "ap2" "(agpkd \"p2\")")
  (action_tile "ap3" "(agpkd \"p3\")")
  (action_tile "ap4" "(agpkd \"p4\")")
  (action_tile "ap5" "(agpkd \"p5\")")
  (action_tile "caltra" "(caltra)")
  (setq listrs (cdr (assoc 'traverssup parametri)))
  (start_list "ltrs") (foreach n listrs (add_list n)) (end_list)
  (setq listri (cdr (assoc 'traversinf parametri)))
  (start_list "ltri") (foreach n listri (add_list n)) (end_list)
  
;;;  (action_tile "n4f" "(compforo \"4f\")")
  (action_tile "ric" "(ricompk)")
  (action_tile "accept" "(legginputk) (done_dialog 1)")
  (action_tile "regdef" "(legginputk) (done_dialog 2)")
  (action_tile "ante" "(legginputk) (vermodk)")
  (action_tile "sal" "(legginputk)")
  (mode_tile "xp1" 2)
  (setq a (start_dialog))
)
(defun vermodk ()
  (if (ssget "x" (list '(0 . "TEXT") '(1 . "NOTA: IL KIT E' VISTO DAL LATO DELLA LANA DI ROCCIA")))
      (progn (setq godis t) (done_dialog 1))
      (progn (alert "Non sei nel prototipo giusto !!") (setq godis nil))
  )
)
(defun ricompk ()
  (setq nr 1)
  (set_tile "desc-kit" desc-kit)
  (foreach n lpk
    (set_tile (strcat "p" (rtos nr 2 0)) (nth 0 n))
    (set_tile (strcat "xp" (rtos nr 2 0)) (rtos (nth 1 n) 2 1))
    (set_tile (strcat "yp" (rtos nr 2 0)) (rtos (nth 2 n) 2 1))
    (mode_tile (strcat "p" (rtos nr 2 0)) 0)
    (mode_tile (strcat "xp" (rtos nr 2 0)) 0)
    (mode_tile (strcat "yp" (rtos nr 2 0)) 0)
    (setq nr (+ 1 nr))
  )
  (setq llunt (reverse llungt))
  (if (car llunt)
    (progn
     (set_tile "ltr1" (rtos (nth 0 (car llunt)) 2 1))
     (set_tile "ptr1" (rtos (nth 1 (car llunt)) 2 1))
     (set_tile "aitr1" (rtos (nth 2 (car llunt)) 2 0))
     (set_tile "aftr1" (rtos (nth 3 (car llunt)) 2 0))
    )
  )
  (if (= 2 (length llunt))
    (progn
     (set_tile "ltr2" (rtos (nth 0 (last llunt)) 2 1))
     (set_tile "ptr2" (rtos (nth 1 (last llunt)) 2 1))
     (set_tile "aitr2" (rtos (nth 2 (last llunt)) 2 0))
     (set_tile "aftr2" (rtos (nth 3 (last llunt)) 2 0))
    )
  )
  (set_tile "ltri" bl_ltri)
  (set_tile "ltrs" bl_ltrs)
)
  
(DEFUN LEGGINPUTk ()
  (setq lpk nil)
  (setq desc-kit (get_tile "desc-kit"))
  
  (setq lpk (cons
	      (list (setq pnome (get_tile "p1")) (atof (get_tile "xp1")) (atof (get_tile "yp1"))
		    (nth 2 (assoc (nth 1 (assoc pnome lispas)) lispan))
		    (nth 3 (assoc (nth 1 (assoc pnome lispas)) lispan)))
	      lpk
	    )
  )
  (if (/= "" (get_tile "p2"))
    (setq lpk (cons
	      (list (setq pnome (get_tile "p2")) (atof (get_tile "xp2")) (atof (get_tile "yp2"))
		    (nth 2 (assoc (nth 1 (assoc pnome lispas)) lispan))
		    (nth 3 (assoc (nth 1 (assoc pnome lispas)) lispan)))

	      
	      lpk
	    )
    )
  )
  (if (/= "" (get_tile "p3"))
    (setq lpk (cons
	      (list (setq pnome (get_tile "p3")) (atof (get_tile "xp3")) (atof (get_tile "yp3"))
		    (nth 2 (assoc (nth 1 (assoc pnome lispas)) lispan))
		    (nth 3 (assoc (nth 1 (assoc pnome lispas)) lispan)))
	      lpk
	    )
    )
  )
  (if (/= "" (get_tile "p4"))
    (setq lpk (cons
	      (list (setq pnome (get_tile "p4")) (atof (get_tile "xp4")) (atof (get_tile "yp4"))
		    (nth 2 (assoc (nth 1 (assoc pnome lispas)) lispan))
		    (nth 3 (assoc (nth 1 (assoc pnome lispas)) lispan)))
	      lpk
	    )
    )
  )
  (if (/= "" (get_tile "p5"))
    (setq lpk (cons
	      (list (setq pnome (get_tile "p5")) (atof (get_tile "xp5")) (atof (get_tile "yp2"))
		    (nth 2 (assoc (nth 1 (assoc pnome lispas)) lispan))
		    (nth 3 (assoc (nth 1 (assoc pnome lispas)) lispan)))
	      lpk
	    )
    )
  )
  (setq seltravinf (nth (atoi (setq bl_ltri (get_tile "ltri")) ) listri))
  (setq seltravsup (nth (atoi (setq bl_ltrs (get_tile "ltrs")) ) listrs))
;;;      (setq llungt (list (list ltrav1 ptrav1 trangin1 trangfi1)))
;;;    )
;;;      (setq llungt (list (list 300 30 90 90)))
  (setq llungt nil)
  (if (/= 0.0 (atof (get_tile "ltr1")))
    (setq llungt (cons (list (atof (get_tile "ltr1")) (atof (get_tile "ptr1")) (atoi (get_tile "aitr1")) (atoi (get_tile "aftr1"))) llungt)))
  (if (/= 0.0 (atof (get_tile "ltr2")))
    (setq llungt (cons (list (atof (get_tile "ltr2")) (atof (get_tile "ptr2")) (atoi (get_tile "aitr2")) (atoi (get_tile "aftr2"))) llungt)))
  (setq lpk (reverse lpk))
)
